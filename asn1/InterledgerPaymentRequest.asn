InterledgerPaymentRequest
DEFINITIONS
AUTOMATIC TAGS ::=
BEGIN

IMPORTS
    UInt8,
    UInt256
    FROM GenericTypes

    InterledgerPacket
    FROM InterledgerPacket
;

InterledgerPaymentRequest ::= SEQUENCE {
    -- IPR Version
    version UInt8,
    -- Cryptographic condition
    condition UInt256,
    -- InterledgerPacket containing InterledgerProtocolPayment
    packet InterledgerPacket
}

END
