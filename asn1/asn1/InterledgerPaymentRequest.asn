InterledgerProtocol
DEFINITIONS
AUTOMATIC TAGS ::=
BEGIN

IMPORTS
    UInt8
    UInt256
    FROM GenericTypes
;

InterledgerPaymentRequest ::= SEQUENCE {
    -- IPR Version
    version UInt8,
    -- Cryptographic condition
    condition UInt256,
    -- ILP Payment Packet
    packet OCTET STRING
}

END
