TrustlineProtocol
DEFINITIONS
AUTOMATIC TAGS ::=
BEGIN

IMPORTS
    UInt8,
    UInt32,
    UInt64,
    UInt128,
    UInt256
    FROM GenericTypes

    Address,
    Timestamp
    FROM InterledgerTypes

    InterledgerPacket
    FROM GenericPacket
;

SideProtocolData ::= SEQUENCE OF SEQUENCE {
  protocolName IA5String,
  protocolData OCTET STRING
}

Ack ::= SEQUENCE {
  correlationId UInt128
}

LocalRequest ::= SEQUENCE {
  messageId UInt128,
  sideProtocolData SideProtocolData
}

LocalResponse ::= SEQUENCE {
  correlationId UInt128,
  sideProtocolData SideProtocolData
}

InterledgerMessageRequest ::= SEQUENCE {
  messageId UInt128,
  packet InterledgerPacket,
  sideProtocolData SideProtocolData
}

InterledgerTransferRequest ::= SEQUENCE {
  transferId UInt128,
  amount UInt64,
  expiresAt Timestamp,
  packet InterledgerPacket
  sideProtocolData SideProtocolData
}

InterledgerMessageResponse ::= SEQUENCE {
  correlationId UInt128,
  packet InterledgerPacket,
  sideProtocolData SideProtocolData
}


CALL ::= CLASS {
    &typeId UInt8 UNIQUE,
    &Type
} WITH SYNTAX {&typeId &Type}

CallSet CALL ::= {
    {1 Ack} |
    {2 LocalRequest} |
    {2 LocalResponse} |
    {3 InterledgerMessageRequest} |
    {3 InterledgerTransferRequest} |
    {4 InterledgerResponse}
}

TrustlineProtocolPacket ::= SEQUENCE {
    -- Unique call identifier
    callId UInt32,
    -- One byte type ID
    type CALL.&typeId ({CallSet}),
    -- Call data
    data CALL.&Type ({CallSet}{@type}),
    -- Enable ASN.1 Extensibility
    extensions SEQUENCE {
        ...
    }
}

END
