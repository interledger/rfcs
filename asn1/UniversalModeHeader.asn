UniversalModeHeader DEFINITIONS AUTOMATIC TAGS ::=
BEGIN

IMPORTS
	Timestamp
	FROM Types
	
	Condition
	FROM CryptoConditions
	
	GenericHeaderPreamble
	FROM GenericExtensionHeaderFormat
;

UniversalModeHeader ::= SEQUENCE {
	preamble GenericHeaderPreamble,
	condition Condition,
	expiresAt Timestamp
}
	
END
