GenericPacket
DEFINITIONS
AUTOMATIC TAGS ::=
BEGIN

IMPORTS
    UInt8,
    VarBytes
    FROM GenericTypes

    TransferRequest,
    SuccessfulTransferResponse,
    FailedTransferResponse
    FROM InterledgerTransferProtocol

    QuoteLiquidityRequest,
    QuoteLiquidityResponse,
    QuoteBySourceAmountRequest,
    QuoteBySourceAmountResponse,
    QuoteByDestinationAmountRequest,
    QuoteByDestinationAmountResponse,
    FailedQuoteResponse
    FROM InterledgerQuotingProtocol
;

PACKET ::= CLASS {
    &typeId UInt8 UNIQUE,
    &Type
} WITH SYNTAX {&typeId &Type}

PacketSet PACKET ::= {
    {1 TransferRequest} |
    {2 SuccessfulTransferResponse} |
    {3 FailedTransferResponse} |
    {4 QuoteLiquidityRequest} |
    {5 QuoteLiquidityResponse} |
    {6 QuoteBySourceAmountRequest} |
    {7 QuoteBySourceAmountResponse} |
    {8 QuoteByDestinationAmountRequest} |
    {9 QuoteByDestinationAmountResponse} |
    {10 FailedQuoteResponse}
}

InterledgerPacket ::= SEQUENCE {
    -- One byte type ID
    type PACKET.&typeId ({PacketSet}),
    -- Length-prefixed header
    data PACKET.&Type ({PacketSet}{@type})
}

END
