InterledgerHeader
DEFINITIONS
AUTOMATIC TAGS ::=
BEGIN

IMPORTS
	Address,
	Amount
	FROM InterledgerTypes
;

InterledgerProtocolHeader ::= SEQUENCE {
	version INTEGER(0..255),
	destinationAddress Address,
	destinationAmount Amount,
	nextHeader INTEGER(0..65535)
}

END
