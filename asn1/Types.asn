Types DEFINITIONS AUTOMATIC TAGS ::=
BEGIN

-- GeneralizedTime is a standard ASN.1 time format based on ISO 8601. It was
-- tempting to use the Unix epoch, however unfortunately, standard POSIX
-- time is discontinuous. If we used POSIX time for expiries for example, a
-- transfer might expire and then un-expire when a leap second occurs. Since
-- Interledger protocols depend on causality, we cannot use POSIX time and
-- since we do not wish to create our own time standard, we end up using ISO
-- 8601.
Timestamp ::= GeneralizedTime

-- A standard interledger address is a hierarchical list of octet strings
Address ::= SEQUENCE OF OCTET STRING

-- A standard interledger amount is a base-10 floating point amount
Amount ::= SEQUENCE {
	exponent INTEGER (-128..127),
	mantissa INTEGER
}
	
END
